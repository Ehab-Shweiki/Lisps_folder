;;---------------------
;; 關於「天正免費插件」
;;---------------------
;; ● 該插件是天正公司發佈的免費插件，供沒有安裝天正發行版的用戶使用，
;;    主要用於打印和閱讀由天正建築TArch、天正水、暖、電等繪製的圖紙；
;; ● 該插件可以在天正官網下載: http://www.tangent.com.cn；
;; ● 該插件可運行於AutoCAD 2010-2020；
;; ● 安裝有天正2010-2020系列相關專業軟件的機器，不需要安裝該插件；
;; ● 它提供了有限的幾個功能，比如轉換為天正低版本的圖紙，供其他人使用；
;;
;; ● 當下載安裝「天正免費插件」完畢，用戶面板中的「天正面板(快捷鍵q7)」就會起作用


;;------------------
;; 天正插件啟動程序
;;------------------
(if (and (<= 15 (fix (atof (getvar "ACADVER"))) 23)
         (setq tmpstr (findfile "tch_kernal.arx"))
    )
(progn
    (arxload tmpstr)
    (setq tmpstr nil)
)
)
