;;;=========================================================================
;;;         源 泉 設 計    用戶自編LSP程序例子
;;;-------------------------------------------------------------------------
;;; 文件夾 sys\用戶文件夾\
;;;
;;;     「用戶文件夾」為自建文件夾。將自編或收集到的「.lsp/.vlx/.arx」程序
;;; 文件放入此文件夾下，再設定此「用戶文件夾」為當前用戶(用命令yq_setuser)，
;;; 則「源泉設計」在啟動的時候會自動加載這些程序。
;;;=========================================================================
;;; 註：1. 此文件是用戶自編LSP程序例子；
;;;     2. 代碼行中分號";"後面是註釋，行首加分號則暫時取消該行。



;;;========================
;;; 一些簡單自定義命令例子
;;;========================

;;; 切換模型/佈局
(defun c:1`()
  (setvar "TILEMODE" (if (= (getvar "TILEMODE") 0) 1 0))
)


;;; 切換圖紙/模型空間
(defun c:``()
  (command (if (yq_ismodelspace) "PSPACE" "MSPACE"))
)

;;----- 新的語句可放在這裡 -----







(princ)  ; 為最後一行
