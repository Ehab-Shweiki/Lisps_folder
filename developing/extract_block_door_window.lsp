(defun get-block-extents (blk / minpt maxpt)
  (vla-getboundingbox blk 'minpt 'maxpt)
  (list (vlax-safearray->list minpt) (vlax-safearray->list maxpt))
)

(defun transform-point (pt blk)
  (vlax-invoke blk 'transformby (vlax-tmatrix (vla-get-blocktransform blk)))
)

(setq pt1 (transform-point minpt blk))
(setq pt2 (transform-point maxpt blk))

(defun local-to-world (blk ptlocal / p)
  ;; blk = VLA block reference (INSERT)
  (setq p (vlax-3d-point ptlocal))
  (vlax-invoke-method blk 'transformby (vlax-tmatrix (vla-get-blocktransform blk)))
  (vlax-get p 'coordinates)
)

(defun get-block-endpoints (ename / blk def obj p1 p2 mat)
  (setq blk (vlax-ename->vla-object ename))
  (setq def (vla-item (vla-get-blocks (vla-get-document blk)) (vla-get-effectivename blk)))
  (setq mat (vlax-get blk 'transformationmatrix))

  (vlax-for obj def
    (if (= (vla-get-objectname obj) "AcDbLine")
      (progn
        (setq p1 (vlax-get obj 'StartPoint)
              p2 (vlax-get obj 'EndPoint))
        (setq wp1 (vlax-variant-value (vlax-invoke obj 'TransformBy mat)))
        (setq wp2 (vlax-variant-value (vlax-invoke obj 'TransformBy mat)))
        (print (list (vlax-safearray->list wp1) (vlax-safearray->list wp2)))
      )
    )
  )
)

(defun c:ExportOpenings ( / sel file)
  (setq sel (ssget "_X" '((0 . "INSERT"))))
  (setq file (open "C:/export/openings.csv" "w"))
  (write-line "Name,X,Y,Z,Rotation,Width,Height,Offset" file)

  (repeat (sslength sel)
    (setq blk (vlax-ename->vla-object (ssname sel 0)))
    (setq name (vla-get-effectivename blk))
    (vla-getboundingbox blk 'pmin 'pmax)
    (setq minpt (vlax-safearray->list pmin))
    (setq maxpt (vlax-safearray->list pmax))
    (setq width (distance (list (car minpt)(cadr minpt)) (list (car maxpt)(cadr maxpt))))
    (setq height (- (caddr maxpt) (caddr minpt)))
    (setq offset (caddr minpt))
    (setq inspt (vlax-get blk 'insertionpoint))
    (setq rot (vlax-get blk 'rotation))
    (write-line
      (strcat name "," (rtos (car inspt) 2 3) "," (rtos (cadr inspt) 2 3) "," (rtos (caddr inspt) 2 3)
              "," (rtos rot 2 3) "," (rtos width 2 3) "," (rtos height 2 3) "," (rtos offset 2 3))
      file)
  )
  (close file)
  (princ "\nExport done to C:/export/openings.csv")
)
