(defun c:CopyBlkPropsToDims ( / ss i blk blkname blkdef ent ed blkcolor)
  (prompt "\nSelect blocks to apply their color to dimension components...")
  (if (setq ss (ssget '((0 . "INSERT"))))
    (progn
      (setq i 0)
      (repeat (sslength ss)
        (setq blk (ssname ss i))
        (setq blkcolor (cdr (assoc 62 (entget blk)))) ; Get block reference color
        (setq blkname (cdr (assoc 2 (entget blk))))
        (setq blkdef (tblobjname "BLOCK" blkname))
        (setq ent (entnext blkdef))
        (while ent
          (setq ed (entget ent))
          (if (wcmatch (cdr (assoc 0 ed)) "*DIMENSION")
            (progn
              ;; Set general color to match block (if not present)
              (if (assoc 62 ed)
                (setq ed (subst (cons 62 blkcolor) (assoc 62 ed) ed))
                (setq ed (append ed (list (cons 62 blkcolor))))
              )
              ;; Override text color
              (if (assoc 176 ed)
                (setq ed (subst (cons 176 blkcolor) (assoc 176 ed) ed))
                (setq ed (append ed (list (cons 176 blkcolor))))
              )
              ;; Override extension line color
              (if (assoc 177 ed)
                (setq ed (subst (cons 177 blkcolor) (assoc 177 ed) ed))
                (setq ed (append ed (list (cons 177 blkcolor))))
              )
              ;; Override dimension line color
              (if (assoc 178 ed)
                (setq ed (subst (cons 178 blkcolor) (assoc 178 ed) ed))
                (setq ed (append ed (list (cons 178 blkcolor))))
              )
              (entmod ed)
            )
          )
          (setq ent (entnext ent))
        )
        (setq i (1+ i))
      )
      (princ "\n✓ Dimension arrows, text, and lines updated using block color.")
    )
    (prompt "\nNo blocks selected.")
  )
  (princ)
)

(defun c:BlkEntitiesToByBlock ( / ss i blk blkname blkdef ent ed)
  (prompt "\nSelect blocks to update all entities (lines, arcs, etc.) to ByBlock properties...")
  (if (setq ss (ssget '((0 . "INSERT"))))
    (progn
      (setq i 0)
      (repeat (sslength ss)
        (setq blk (ssname ss i))
        (setq blkname (cdr (assoc 2 (entget blk))))
        (setq blkdef (tblobjname "BLOCK" blkname))
        (setq ent (entnext blkdef))
        (while ent
          (setq ed (entget ent))
          (if (member (cdr (assoc 0 ed)) '("LINE" "ARC" "CIRCLE" "LWPOLYLINE" "POLYLINE" "SPLINE" "ELLIPSE"))
            (progn
              ;; Set color to ByBlock
              (if (assoc 62 ed)
                (setq ed (subst (cons 62 0) (assoc 62 ed) ed))
                (setq ed (append ed (list (cons 62 0))))
              )
              ;; Set linetype to ByBlock
              (if (assoc 6 ed)
                (setq ed (subst (cons 6 "ByBlock") (assoc 6 ed) ed))
                (setq ed (append ed (list (cons 6 "ByBlock"))))
              )
              ;; Set lineweight to ByBlock (-1)
              (if (assoc 370 ed)
                (setq ed (subst (cons 370 -1) (assoc 370 ed) ed))
                (setq ed (append ed (list (cons 370 -1))))
              )
              ;; Optional: Set transparency (440) to ByBlock
              (if (assoc 440 ed)
                (setq ed (subst (cons 440 0) (assoc 440 ed) ed))
                (setq ed (append ed (list (cons 440 0))))
              )
              ;; Apply changes
              (entmod ed)
            )
          )
          (setq ent (entnext ent))
        )
        (setq i (1+ i))
      )
      (princ "\n✓ All visual properties of line/arc/etc. entities inside blocks set to ByBlock.")
    )
    (prompt "\nNo blocks selected.")
  )
  (princ)
)
